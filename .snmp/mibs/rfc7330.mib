BFD-TC-STD-MIB DEFINITIONS ::= BEGIN

    IMPORTS
        MODULE-IDENTITY, mib-2, Unsigned32
            FROM SNMPv2-SMI                               -- [RFC2578]

        TEXTUAL-CONVENTION
            FROM SNMPv2-TC;                               -- [RFC2579]

    bfdTCStdMib MODULE-IDENTITY
        LAST-UPDATED
                   "201404131200Z" -- 13 April 2014 12:00:00 EST

        ORGANIZATION "IETF Bidirectional Forwarding Detection
                      Working Group"
        CONTACT-INFO
            "Thomas D. Nadeau
             Brocade
             Email:  tnadeau@lucidvision.com

             Zafar Ali
             Cisco Systems, Inc.
             Email:  zali@cisco.com

             Nobo Akiya
             Cisco Systems, Inc.
             Email:  nobo@cisco.com

             Comments about this document should be emailed directly
             to the BFD working group mailing list at
             rtg-bfd@ietf.org"

        DESCRIPTION
          "Copyright (C) The IETF Trust (2014). The initial version
           of this MIB module was published in RFC xxxx. For full legal
           notices see the RFC itself. Supplementary information
           may be available on:
           http://www.ietf.org/copyrights/ianamib.html"

    -- RFC Ed.: RFC-editor pls fill in xxxx

        REVISION "201404131200Z" -- 13 April 2014 12:00:00 EST
        DESCRIPTION
          "Initial version. Published as RFC xxxx."

    -- RFC Ed.: RFC-editor pls fill in xxxx

    ::= { mib-2 223 }

    -- RFC Ed.: RFC-editor pls fill in XXX, see section 5 for details

    BfdSessIndexTC ::= TEXTUAL-CONVENTION
    DISPLAY-HINT   "d"
    STATUS         current
    DESCRIPTION
        "An index used to uniquely identify BFD sessions."
    SYNTAX Unsigned32 (1..4294967295)

    BfdIntervalTC ::= TEXTUAL-CONVENTION
    DISPLAY-HINT  "d"
    STATUS        current
    DESCRIPTION
        "The BFD interval in microseconds."
    SYNTAX Unsigned32 (0..4294967295)

    BfdMultiplierTC ::= TEXTUAL-CONVENTION
    DISPLAY-HINT    "d"
    STATUS          current
    DESCRIPTION
        "The BFD failure detection multiplier."
    SYNTAX Unsigned32 (1..255)

    BfdCtrlDestPortNumberTC ::= TEXTUAL-CONVENTION
    DISPLAY-HINT            "d"
    STATUS                  current
    DESCRIPTION
        "UDP destination port number of BFD control packets.
         3784 represents single hop BFD session.
         4784 represents multi hop BFD session.
         6784 represents BFD on LAG session.
         However, syntax is left open to wider range of values
         purposely for two reasons:
         1. Implementation uses non-compliant port number for
            valid proprietary reason.
         2. Potential future extension drafts.

         The value of 0 is a special, reserved value used
         to indicate special conditions and should not be considered
         a valid port number."
    REFERENCE
        "Use of port 3784 from Katz, D. and D. Ward,
              Bidirectional Forwarding Detection (BFD) for
              IPv4 and IPv6 (Single Hop), RFC 5881, June 2010.

         Use of port 4784 from Katz, D. and D. Ward,
              Bidirectional Forwarding Detection (BFD) for
              Multihop Paths, RFC 5883, June 2010.

         Use of port 6784 from Bhatia, M., Chen, M., Boutros, S.,
              Binderberger, M., and J. Haas, Bidirectional Forwarding
              Detection (BFD) on Link Aggregation Group (LAG)
              Interfaces, RFC 7130, February 2014."
    SYNTAX Unsigned32 (0..65535)

    BfdCtrlSourcePortNumberTC ::= TEXTUAL-CONVENTION
    DISPLAY-HINT              "d"
    STATUS                    current
    DESCRIPTION
        "UDP source port number of BFD control packets.
         However, syntax is left open to wider range of values
         purposely for two reasons:
         1. Implementation uses non-compliant port number for
            valid proprietary reason.
         2. Potential future extension drafts.

         The value of 0 is a special, reserved value used
         to indicate special conditions and should not be considered
         a valid port number."
    REFERENCE
        "Port 49152..65535 from RFC5881"

    SYNTAX Unsigned32 (0..65535)

    END
