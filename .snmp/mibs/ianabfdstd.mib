IANA-BFD-TC-STD-MIB DEFINITIONS ::= BEGIN
    IMPORTS
        MODULE-IDENTITY, mib-2
            FROM SNMPv2-SMI                               -- [RFC2578]

        TEXTUAL-CONVENTION
            FROM SNMPv2-TC;                               -- [RFC2579]

    ianaBfdTCStdMib MODULE-IDENTITY
        LAST-UPDATED
                   "201404131200Z" -- 13 April 2014 12:00:00 EST
        ORGANIZATION
                   "IANA"
        CONTACT-INFO
                   "Internet Assigned Numbers Authority
                    Postal: 4676 Admiralty Way, Suite 330
                            Marina del Rey, CA 90292
                    Tel:    +1 310 823 9358
                    E-Mail: iana@iana.org"

        DESCRIPTION
          "Copyright (C) The IETF Trust (2014). The initial version
           of this MIB module was published in RFC xxxx. For full legal
           notices see the RFC itself. Supplementary information
           may be available on:
           http://www.ietf.org/copyrights/ianamib.html"

    -- RFC Ed.: RFC-editor pls fill in xxxx

        REVISION
          "201404131200Z" -- 13 April 2014 12:00:00 EST
        DESCRIPTION
          "Initial version. Published as RFC xxxx."

    -- RFC Ed.: RFC-editor pls fill in xxxx

    ::= { mib-2 224 }

    -- RFC Ed.: RFC-editor pls fill in YYY, see section 5 for details

    IANAbfdDiagTC ::= TEXTUAL-CONVENTION
    STATUS       current
    DESCRIPTION
        "A common BFD diagnostic code."
    REFERENCE
        "Katz, D. and D. Ward, Bidirectional Forwarding
              Detection (BFD), RFC 5880, June 2010.

         Allan, D., Swallow, G., and Drake, J., Proactive Connectivity

              Verification, Continuity Check, and Remote Defect
              Indication for the MPLS Transport Profile, RFC 6428,
              November 2011."
    SYNTAX INTEGER {
        noDiagnostic(0),
        controlDetectionTimeExpired(1),
        echoFunctionFailed(2),
        neighborSignaledSessionDown(3),
        forwardingPlaneReset(4),
        pathDown(5),
        concatenatedPathDown(6),
        administrativelyDown(7),
        reverseConcatenatedPathDown(8),
        misConnectivityDefect(9)
    }

    IANAbfdSessTypeTC ::= TEXTUAL-CONVENTION
    STATUS        current
    DESCRIPTION
        "BFD session type"
    REFERENCE
        "Katz, D. and D. Ward, Bidirectional Forwarding
              Detection (BFD), RFC 5880, June 2010.

         Katz, D. and D. Ward, Bidirectional Forwarding
              Detection (BFD) for IPv4 and IPv6 (Single Hop),
              RFC 5881, June 2010.

         Katz, D. and D. Ward, Bidirectional Forwarding
              Detection (BFD) for Multihop Paths, RFC 5883,
              June 2010."
    SYNTAX INTEGER {
        singleHop(1),
        multiHopTotallyArbitraryPaths(2),
        multiHopOutOfBandSignaling(3),
        multiHopUnidirectionalLinks(4)
    }

    IANAbfdSessOperModeTC ::= TEXTUAL-CONVENTION
    STATUS            current
    DESCRIPTION
        "BFD session operating mode"
    REFERENCE
        "Katz, D. and D. Ward, Bidirectional Forwarding
              Detection (BFD), RFC 5880, June 2010."
    SYNTAX INTEGER {
        asyncModeWEchoFunction(1),
        asynchModeWOEchoFunction(2),
        demandModeWEchoFunction(3),
        demandModeWOEchoFunction(4)
    }

    IANAbfdSessStateTC ::= TEXTUAL-CONVENTION
    STATUS         current
    DESCRIPTION
        "BFD session state. State failing(5) is only applicable if
         corresponding session is running in BFD version 0."
    REFERENCE
        "RFC 5880 - Bidirectional Forwarding Detection (BFD), Katz,
         D., Ward, D., June 2010."
    SYNTAX INTEGER {
        adminDown(1),
        down(2),
        init(3),
        up(4),
        failing(5)
    }

    IANAbfdSessAuthenticationTypeTC ::= TEXTUAL-CONVENTION
    STATUS                      current
    DESCRIPTION
        "BFD authentication type"
    REFERENCE
        "Sections 4.2 - 4.4 from Katz, D. and D. Ward,
         Bidirectional Forwarding Detection (BFD),
         RFC 5880, June 2010."
    SYNTAX INTEGER {
        noAuthentication(-1),
        reserved(0),
        simplePassword(1),
        keyedMD5(2),
        meticulousKeyedMD5(3),
        keyedSHA1(4),
        meticulousKeyedSHA1(5)
    }

    IANAbfdSessAuthenticationKeyTC ::= TEXTUAL-CONVENTION
    DISPLAY-HINT                  "1x "
    STATUS                        current
    DESCRIPTION
        "BFD authentication key type.

         An IANAbfdSessAuthenticationKeyTC is always interpreted
         within the context of an IANAbfdSessAuthenticationTypeTC
         value.  Every usage of the IANAbfdSessAuthenticationTypeTC
         textual convention is required to specify the





         IANAbfdSessAuthenticationKeyTC object that provides the
         context.  It is suggested that the
         IANAbfdSessAuthenticationKeyTC object be logically registered
         before the object(s) that use the
         IANAbfdSessAuthenticationKeyTC textual convention, if they
         appear in the same logical row.

         The value of a IANAbfdSessAuthenticationKeyTC must
         always be consistent with the value of the associated
         IANAbfdSessAuthenticationTypeTC object.  Attempts to set a
         IANAbfdSessAuthenticationKeyTC object to a value inconsistent
         with the associated IANAbfdSessAuthenticationTypeTC must fail
         with an inconsistentValue error.

         The following size constraints for a
         IANAbfdSessAuthenticationKeyTC object are defined for the
         associated IANAbfdSessAuthenticationTypeTC values show below:

         noAuthentication(-1): SIZE(0)
         reserved(0): SIZE(0)
         simplePassword(1): SIZE(1..16)
         keyedMD5(2): SIZE(16)
         meticulousKeyedMD5(3): SIZE(16)
         keyedSHA1(4): SIZE(20)
         meticulousKeyedSHA1(5): SIZE(20)

         When this textual convention is used as the syntax of an
         index object, there may be issues with the limit of 128
         sub-identifiers specified in SMIv2, STD 58.  In this case,
         the object definition MUST include a 'SIZE' clause to limit
         the number of potential sub-identifiers; otherwise
         the applicable constraints MUST be stated in the appropriate
         conceptual row DESCRIPTION clauses, or in the surrounding
         documentation if there is no single DESCRIPTION clause that
         is appropriate."
    REFERENCE
        "RFC5880, Sections 4.2 - 4.4"
    SYNTAX OCTET STRING(SIZE(0..252))

    END
